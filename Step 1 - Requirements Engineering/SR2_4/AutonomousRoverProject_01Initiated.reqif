# AutonomousRoverCaseStudyRequirementsDocuments
Project compiling stakeholder and system requirements

# Specification: Autonomous Rover SyRS
- ReqIF.Description: System Requirements Specification for the Polarsys Autonomous Rover Case Study
- ReqIF.Name: Autonomous Rover SyRS

## 1: Introduction (SystemRequirement)
- Type: Title

### 2: Purpose (SystemRequirement)
- Type: Title

### 3: Document conventions (SystemRequirement)
- Type: Title

### 4: Intended audience (SystemRequirement)
- Type: Title

### 5: Additional information (SystemRequirement)
- Type: Title

### 6: Contact information/SyRS team members (SystemRequirement)
- Type: Title

### 7: References (SystemRequirement)
- Type: Title

## 8: System overview (SystemRequirement)
- Type: Title

### 9: System context (SystemRequirement)
- Type: Title

### 10: System functions (SystemRequirement)
- Type: Title

### 11: User characteristics (SystemRequirement)
- Type: Title

## 12: Functional Requirements (SystemRequirement)
- Type: Title

### 35 (SystemRequirement)
The Rover must support various payloads (sensors/camera/robotic arm) thanks to a pluggable software architecture
- Compliance: Compliant
- ReqtStatus: Ready
- Target Version: 1.0
- Type: Requirement

### 36 (SystemRequirement)
The Rover must explore a flat room (without holes) autonomously
- Compliance: Compliant
- ReqtStatus: Ready
- Target Version: 1.0
- Type: Requirement
- System Requirements Links -> 55

### 37 (SystemRequirement)
The Rover must report a map of the explored environment
- Compliance: Compliant
- ReqtStatus: Ready
- Target Version: 1.0
- Type: Requirement
- System Requirements Links -> 61

### 46 (SystemRequirement)
The Rover must avoid crash in obstacles
- Compliance: Compliant
- ReqtStatus: Ready
- Target Version: 2.0
- Type: Requirement
- System Requirements Links -> 60

### 48 (SystemRequirement)
The Rover must provide images of the explored environment
- Compliance: Compliant
- ReqtStatus: Ready
- Target Version: 3.0
- Type: Requirement
- System Requirements Links -> 63

### 49 (SystemRequirement)
The Rover must differentiate walls from inclined pathway
- Compliance: Compliant
- ReqtStatus: Ready
- Target Version: 3.0
- Type: Requirement
- System Requirements Links -> 62

### 50 (SystemRequirement)
The Rover must avoid falling on its backside
- Compliance: Compliant
- ReqtStatus: Ready
- Target Version: 3.0
- Type: Requirement
- System Requirements Links -> 73

## 13: Usability Requirements (SystemRequirement)
- Type: Title

## 14: Performance Requirements (SystemRequirement)
- Type: Title

### 40 (SystemRequirement)
Battery must provide an autonomy of at least 10mn
- Compliance: Compliant
- Notes: Will evolve to 30mn autonomy in V3.0
- ReqtStatus: Ready
- Target Version: 1.0
- Type: Requirement
- System Requirements Links -> 54

### 51 (SystemRequirement)
Battery must provide an autonomy of at least 30mn
- Compliance: Compliant
- ReqtStatus: Ready
- Target Version: 3.0
- Type: Requirement
- System Requirements Links -> 59

## 15: System Interfaces (SystemRequirement)
- Type: Title

## 16: System Operations (SystemRequirement)
- Type: Title

### 17: Human system integration requirements (SystemRequirement)
- Type: Title

#### 45 (SystemRequirement)
The Rover must be controlled through an Android application
- Compliance: Compliant
- ReqtStatus: Ready
- Target Version: 2.0
- Type: Requirement
- System Requirements Links -> 57

#### 47 (SystemRequirement)
The Rover must be controlled through an IoS application
- Compliance: Compliant
- ReqtStatus: Ready
- Target Version: 3.0
- Type: Requirement
- System Requirements Links -> 58

### 18: Maintainability (SystemRequirement)
- Type: Title

### 19: Reliability (SystemRequirement)
- Type: Title

## 20: System modes and states (SystemRequirement)
- Type: Title

## 21: Physical characteristics (SystemRequirement)
- Type: Title

### 22: Physical requirements (SystemRequirement)
- Type: Title

#### 38 (SystemRequirement)
The Rover must be built with the 2 motor Dagu Electronics Rover 5 robot chassis with encoders. (https://www.pololu.com/product/1551)
- Compliance: Compliant
- Notes: The Dagu 5 platform with encoders is to be used.
- ReqtStatus: Ready
- Target Version: 1.0
- Type: Requirement
- System Requirements Links -> 46
- System Requirements Links -> 29

#### 39 (SystemRequirement)
The Rover must be built with widely available hardware pieces (Arduino, Raspberry Pi)
- Compliance: Compliant
- ReqtStatus: Ready
- Target Version: 1.0
- Type: Requirement
- System Requirements Links -> 72

#### 41 (SystemRequirement)
The Rover must be assembled with limited soldering capabilities
- Compliance: Compliant
- ReqtStatus: Ready
- Target Version: 1.0
- Type: Requirement
- System Requirements Links -> 70

### 23: Adaptability requirements (SystemRequirement)
- Type: Title

## 24: Environmental conditions (SystemRequirement)
- Type: Title

### 44 (SystemRequirement)
The Rover must explore dangerous areas (with many obstacles/holes, Ö)
- Compliance: Compliant
- ReqtStatus: Ready
- Target Version: 2.0
- Type: Requirement
- System Requirements Links -> 68

## 25: System security (SystemRequirement)
- Type: Title

## 26: Information management (SystemRequirement)
- Type: Title

## 27: Policies and regulations (SystemRequirement)
- Type: Title

## 28: System life cycle sustainment (SystemRequirement)
- Type: Title

### 43 (SystemRequirement)
The total price of the Rover, without the sensor payload and sensor mounts, must be less than 200$
- Compliance: Compliant
- ReqtStatus: Ready
- Type: Requirement
- System Requirements Links -> 65

## 29: Packaging, handling, shipping and transportation (SystemRequirement)
- Type: Title

### 42 (SystemRequirement)
The Rover must be packageable for flight travel (less than 10Kg including a flight case, handluggage max dimensions)
- Compliance: Compliant
- ReqtStatus: Ready
- Target Version: 1.0
- Type: Requirement
- System Requirements Links -> 67

## 30: Verification (SystemRequirement)
- Type: Title

## 31: Assumptions and dependencies (SystemRequirement)
- Type: Title

## 32: Other Requirements (SystemRequirement)
- Type: Title

## 33: Appendix A: Terminology/Glossary/Definitions list (SystemRequirement)
- Type: Title

## 34: Appendix B: Requirements Traceability Matrix (SystemRequirement)
- Type: Title

# Specification: Autonomous Rover StRS
- ReqIF.Description: Autonomous Rover System Stakeholder Requirements Specification
- ReqIF.Name: Autonomous Rover StRS

## 1: Introduction (StakeholderRequirement)

### 2: Business purpose (StakeholderRequirement)

#### 47 (StakeholderRequirement)
The Acquirer is an Emergency Hazardous Material (HazMat) Response organization. They assist police, fire departments and emergency medical services when they need to operate in a potentially hazardous environment. The HazMat Response Team enter potentially dangerous environments to: 1) assess the presence of hazardous material on a crime or fire scene; 2) evaluate the nature and extent of the hazardous material danger.

#### 121 (StakeholderRequirement)
The data will allow respondants to properly respond to emergency situation and apply tthe proper HazMat protocols and protections.

### 3: Business scope (StakeholderRequirement)

#### 86 (StakeholderRequirement)
The HazMat Response team is a unit which reports to the regional government public security and safety agency.

### 4: Business overview (StakeholderRequirement)

#### 87 (StakeholderRequirement)
The unit supports regional and local police, fire and emergency response units. It can also be called in by national agencies and armed forces.

### 5: Definitions (StakeholderRequirement)

#### 122: Hazardous Material (StakeholderRequirement)

##### 128 (StakeholderRequirement)
Hazardous Materials, also known as HazMat our dangerous goods are solids, liquids, or gases that can harm people, other living organisms, property, or the environment. They are often subject to chemical regulations. In the United States and sometimes in Canada, dangerous goods are more commonly known as hazardous materials, (abbreviated as HAZMAT or HazMat). "HazMat teams" are personnel specially trained to handle dangerous goods. Dangerous goods include materials that are radioactive, flammable, explosive, corrosive, oxidizing, asphyxiating, biohazardous, toxic, pathogenic, or allergenic. Also included are physical conditions such as compressed gases and liquids or hot materials, including all goods containing such materials or chemicals, or may have other characteristics that render them hazardous in specific circumstances.
https://en.wikipedia.org/wiki/Dangerous_goods

### 6: Stakeholders (StakeholderRequirement)

#### 98: Acquirer (StakeholderRequirement)

##### 99 (StakeholderRequirement)
The acquirer is a regional Hazardous Material Emergency Response Unit operating under the authority of the regional government..

#### 84: Hazardous Material Emergy Response Technician (StakeholderRequirement)

##### 91 (StakeholderRequirement)
The Hazardous Material Emergency Response Technician is the sole person allowed and trained to deploy, operate and recover the Rover. Depending on the situation, the unit may dispatch one or two Hazmat Emergency Response Technician into a theater of operations.

#### 85: Maintenance Technician (StakeholderRequirement)

##### 92 (StakeholderRequirement)
The Emergency Response unit has one Maintenance Technician on staff that will be qualified to perform any maintenance on the Rover. The maintenance technician is capable of performing basic electronics soldering and assembly. The technician, however, is not qualified to perform high-reliability soldering or "clean room" fabrication/assembly tasks.

##### 97 (StakeholderRequirement)
The Maintenance Technician will not be required, nor is he expected, to be able to re-program the Autonomous Rover.

##### 93 (StakeholderRequirement)
The Maintenance Technician will never be dispatched to a theater of operations.

#### 88: Supported Emergy Services Unit (StakeholderRequirement)

##### 89 (StakeholderRequirement)
Other than for training exercises, the HazMat response team will always operate in support of a unit requesting their services. The unit can either be law enforcement, fire protection, emergency medical service or armed forces.

##### 90 (StakeholderRequirement)
The HazMat Emergency Response Unit will not provide "live" data, nor will they transfer any of the data from the Rover to the supported unit on site. If such a requirement exists, they will acquire the data through usual Request for Information submission administrative channels.

##### 100 (StakeholderRequirement)
A number of units have expressed a need to monitor Autonomous Rover sensor data or imagery "live" during a mission. This capability may be incorporated at a later time.

## 7: References (StakeholderRequirement)

## 8: Business management requirements (StakeholderRequirement)

### 9: Business environment (StakeholderRequirement)

#### 94 (StakeholderRequirement)
The business environment of the Autonomous Rover is an indoor operating theater in which the presence of Hazardous Materials is suspected. The operating environment may be under, special circumstances, an outdoor location, with the understanding that the Autonomous Rover is not designed for that type of environment.

### 10: Goal and objective (StakeholderRequirement)

#### 95 (StakeholderRequirement)
The Autonomous Rover is being acquired to help ensure emergency response personnel are not sent into an unsafe operating scene.

### 11: Business model (StakeholderRequirement)

#### 123 (StakeholderRequirement)
The Autonomous Rover is operated as a public service, under regional authority funding.

#### 124 (StakeholderRequirement)
If a non-governemental organization requests the services of the Autonomous Rover and HazMat Response Team, they must negotiate a contract with the regional

### 12: Information environment (StakeholderRequirement)

#### 96 (StakeholderRequirement)
The Autonomous Rover will not be connected into any networks during the course of normal operations other than a "tether" connection to allow the HazMat Response TEchnician to control the rover remotely.

## 13: Business operational requirements (StakeholderRequirement)

### 14: Business processes (StakeholderRequirement)

#### 101 (StakeholderRequirement)
Hazardous Material Emergency Response Unit processes and operating procedures will remain unchanged.

### 15: Business operational policies and rules (StakeholderRequirement)

#### 69: Human Resources (StakeholderRequirement)

##### 70 (StakeholderRequirement)
The Emergency Response Team has one electronic maintenance technician. This technician, however, is not qualified to perform high-reliability soldering. All electronic assemblies, therefore, must only require limited, general purpose soldering capabilities and abilities.

#### 71: Information Technologies and Software (StakeholderRequirement)

##### 72 (StakeholderRequirement)
The administration under which the Emergency Response Team operates hasadopted an Open-Source software and Commercial-Off-the-Shelf (COTS) component usage policy. The Autonomous Rover must respect those rules to the maximum extent practicable.

### 16: Business operational constraints (StakeholderRequirement)

#### 125 (StakeholderRequirement)
The operating procedures of the Autonmous Rover must be negotiated with each of the emergency response units to ensure operations can be carried out safely at all times.

### 17: Business operational modes (StakeholderRequirement)

#### 126 (StakeholderRequirement)
Autonomous Rover operations will go through the following cycle:
- HazMat Team scramble and dispatch;
- Transit to scene;
- Mission coordination and briefing with emergency response team;
- Mission and Autonomous Rover preparation;
- Mapping and sensor scan mission execution;
- Data collection and mission debrief;
- Autonmous Rover stowage;
- Egress back to base;
- Mission report preparation and debrief.

### 18: Business operational quality (StakeholderRequirement)

#### 127 (StakeholderRequirement)
The following metrics will be collected from each dispatched mission:
- Completion status: Success, Partial success, Aborted or Failure;

### 19: Business structure (StakeholderRequirement)

#### 129 (StakeholderRequirement)
The HazMat Response Team integrates into the Emergency Response system command hierarchy. They always report to the on-site command team in accordance with established command and control protocols and procedures.

## 20: User requirements (StakeholderRequirement)

### 27 (StakeholderRequirement)
The primary use is the HazMat Response Technician. First and foremost, he/she wants the Autonomous Rover to be easy to use. It should be possible to learn its operation in no more than a one (1) training session. The technician should become totally proficient with all operational aspects of the Autonomous Rover in no more than five (5) training exercices. An Autonomous Rover stowed in its transport case must be transportable by a single person.

## 21: Concept of proposed system (StakeholderRequirement)

### 22: Operational concept (StakeholderRequirement)

#### 66: Mobility (StakeholderRequirement)

##### 67 (StakeholderRequirement)
The Emergency Response Service is required to support remote location operations reached by air. It cannot, therefore, weigh more than 10kg, including a large enough transport flight case. The maximum dimensions of the flight case must be within airline allowed hand luggage.

### 23: Operational scenario (StakeholderRequirement)

#### 76: Deployment to the Theatre of Operations (StakeholderRequirement)

##### 82 (StakeholderRequirement)
The Hazardous Material Response Team will dispatch to the theater of operations by road or air. The Autonomous Rover, batteries (including spare batteries and battery charger, if required) sensor payloads and critical spare parts will be transported in the air transport case.

##### 83 (StakeholderRequirement)
Because it is never known where a mission can be dispatched from, it is necessary to carry all sensors along with the rover.

#### 77: Pre-operation Autonomous Rover Preparation (StakeholderRequirement)

##### 104 (StakeholderRequirement)
Once having reached the site where the mission will be performed, the Emergency Response Technician will assemble the Autonomous Rover, adjust the chassis height, mount the sensors needed for the mission, power-up the Autonomous Rover and perform a power-up check and battery level verification.

##### 113 (StakeholderRequirement)
The Autonomous Rover should either be able to automatically recognize connected sensors or provide a means for the HazMat Respeonse Technician to enter the sensor configuration once they are mounted.

#### 78: Theatre Mapping and Data Collection (StakeholderRequirement)

##### 105 (StakeholderRequirement)
Once the HazMat Response Technician is satisfied the Autonomous Rover is ready for the mission, he/she will position the rover for the mission in one of two ways:

###### 106 (StakeholderRequirement)
- In Phase 1 deployment, the technician will position by hand the rover at the starting point of the zone to be explored;

###### 107 (StakeholderRequirement)
- in subsequent deployment phases, the technician will have the option to use the tablet remote control device to position the rover at the starting point of the zone to be explored.

##### 108 (StakeholderRequirement)
During the mission, since the technician will likely not have a direct sight to the rover, it is not desirable that it be possible to steer the robot remotely in anmy way.

##### 120 (StakeholderRequirement)
During the mission the Autonomous Rover should adopt an avoidance and evasion strategy if it encounters a threat. For example, if the rover is capable of detecting a fire and encouters one it will steer to stay at a distance of the fire. Similarly, if is capable of detecting a water hazard, it will avoid the water hazard rather than attempt to go through it.

##### 109 (StakeholderRequirement)
Once the rover has completed the mapping and data collection mission, it is to return to the starting point where it was placed

##### 111 (StakeholderRequirement)
In Deployment phase 2 and beyond, it would be desirable that the HazMat Response Technician be able to abort a mission. In that instance, the Autonomous Rover interrupts the mission returns to the point of departure.

##### 119 (StakeholderRequirement)
The HazMat Response Technician retrieves the Autonomous Rover at the end of the mission.

#### 79: Post-Operation Data Download (StakeholderRequirement)

##### 110 (StakeholderRequirement)
Once a mission has been completed and the Autonomous Rover has been returned to a secure location, the HazMat Response Technician downloads the map and sensor data from the Autonomous Rover to the remote control tablet. In the Deployment Phase 1 Autonomous Rover, thie download can be done using a cable connection to the Autonomous Rover.

#### 80: Autonomous Rover Operational Software Download/Upgrade (StakeholderRequirement)

#### 81: Autonomous Rover Maintenance (StakeholderRequirement)

##### 102: Autonomous Rover Re-programming (StakeholderRequirement)

###### 112 (StakeholderRequirement)
It is not expected, under normal circumstances, that the Autonomous Rover operational software be loaded, modified or upgraded in the field. This operation will normally be performed by the Autonomous Rover supplier.

##### 103: Autonomous Rover Maintenance and Repair (StakeholderRequirement)

###### 114: Field Maintenance and Repair (StakeholderRequirement)

###### 116 (StakeholderRequirement)
The HazMat Response Technician needs to be able to perform light field repairs such as replacing rover tracks, switching sensors and swapping batteries.

###### 117 (StakeholderRequirement)
The Autonomous Rover is considered an expendable vehicle, therefore, no heavy maintenance will be expected on it, such as replacing a track drive motor or repairing significant chassis casing fractures.

###### 115: Shop Maintenance and Repair (StakeholderRequirement)

###### 118 (StakeholderRequirement)
The HazMat Emergency Response Unit maintenance technician will perform light repairs such as swapping the rover chassis, controller board, re-soldering disconnected wires and such.

## 24: Project Constraints (StakeholderRequirement)

### 46 (StakeholderRequirement)
The Acquirer is imposing three (3) main constraints on the Autonomous Rover project: first, cost; second, the Autonomous Rover will be deployed in four (4) phases; and third, they have selected the Dagu Rover 5 chassis as a standard chassis for all their small robot and rover applications.

### 64: Autonomous Rover Unit Cost (StakeholderRequirement)

#### 65 (StakeholderRequirement)
The Emergency Response Service has determined that the unit cost of the Autonomous Rover must not exceed $200. This does not include the unit cost of the sensors or sensor nounts.

### 48: Phased Deployment (StakeholderRequirement)

#### 49: Phase 1 Deployment (StakeholderRequirement)

##### 52 (StakeholderRequirement)
In this initial deployment phase, only the Autonomous Rover will be made available (i.e. no remote controller). All control actions are to be done on the rover itself using buttons or a simple panel.

##### 53 (StakeholderRequirement)
The Autonomous Rover must be able to carry a mission payload consisting of as many as three (3) of any of the following sensors, which it will power and collect/store data from for the duration of the mission:
- IR Sensor;
- explosive gas sensor;
- smoke sensor;
- ammonia sensor;
- IR range finder;
- acoustic range finder;
- radioactivity sensor;
- water/liquid sensor;
- light sensor;
- carbon monoxide sensor;
- vertical boom.

##### 54 (StakeholderRequirement)
The Autonomous Rover must be able to carry-out a minimum 10 minute scan and data collection mission, including the return to the start point.

##### 61 (StakeholderRequirement)
The Autonomous Rover must construct and report a map of the theatre of operations, identifying the dimension of the zone it has inspected.

##### 55 (StakeholderRequirement)
The mission will take place in a flat, obstacle-free room the size of a typica two-car garage.

##### 56 (StakeholderRequirement)
The test mission will be run with the worst-case sensor payload in terms of the data tranfer rate and storage space requirements with sensor data collection running for the complete length of the mission.

#### 50: Phase 2 Deployment (StakeholderRequirement)

##### 57 (StakeholderRequirement)
In phase 2 deployment, the Acquirer wants to be able to remote control the Autonomous Rover using an Android Tablet and application.

##### 59 (StakeholderRequirement)
In phase 2, the Autonomous Rover must be able to carry-out a minimum 30 minute scan and data collection mission, including the return to the start point.

##### 60 (StakeholderRequirement)
In phase 2, the Autonomous Rover must be able to avoid obstacles and record their location on the theatre map.

##### 68 (StakeholderRequirement)
In phase 2, the Autonomous Rover must be able to navigate through holes or depressions in the surface of the theatre.

#### 51: Phase 3 Deployment (StakeholderRequirement)

##### 58 (StakeholderRequirement)
In phase 3 deployment, the Acquirer wants to be able to remote control the Autonomous Rover using an Apple iPad Tablet running an iOS application.

##### 63 (StakeholderRequirement)
In phase 3, the Autonomous Rover must be able to carry a digital colour camera (e.g. GoPro). The Autonomous Rover is not required to collect and store images and videos from this sensor.

##### 62 (StakeholderRequirement)
In phase 3, the Autonomous Rover must be able to navigate up and down inclined ramps. In doing so, it must be able to distinguish between inclined pathways and walls.

##### 73 (StakeholderRequirement)
Since it is unlikely the Autonomous Rover will be recoverable if it flips over, it must limit its operations so as not to flip over.

#### 74: Phase 4 Deployment (StakeholderRequirement)

##### 75 (StakeholderRequirement)
The Acquirer has included schedule provisions for a fourth and final phase. There are no known needs for that phase at this time. Any needs for the phase will be processed through the the Supplier's Change Control process.

### 28: Dagu Rover 5 with Encoders (StakeholderRequirement)

#### 29 (StakeholderRequirement)
The Dagu Rover 5 chassis from Dagu Electronics makes a great base for building a small tank-like RC vehicle or autonomous robot. The chassis includes a battery holder and two DC motors, with an independent drive train and a quadrature encoder for each tread, so all you need to add to make a complete robot is a robot controller and the sensors of your choosing. A unique mechanism allows its user to configure the clearance of the chassis by adjusting the angle of the gearbox assemblies.

#### 30: Specifications (StakeholderRequirement)

##### 31 (StakeholderRequirement)
The Rover 5 tracked chassis, made by Dagu Electronics, is a durable robot platform with caterpillar treads that let it drive over many types of surfaces and uneven terrain. All you need to get the chassis moving is a robot controller or motor controller to drive the two built-in DC motors, which powered by the included 6-AA battery holder (AA batteries sold separately). A small Phillips screwdriver and an Allen wrench are included for working with the chassis.

##### 32 (StakeholderRequirement)
The chassis features a rugged white plastic body with room to house the included battery holder and some additional electronics. The two powerful motors with 86.8:1 gearboxes are strong enough to lift the weight of the chassis and allow it to achieve speeds as high as 10 in/s (25 cm/s). The Rover 5 is offered in two versions: with and without quadrature encoders; the encoders provide a resolution of 1000 counts per three revolutions of the wheel, or 333.33 CPR (counting both rising and falling edges of both encoder channels).

##### 34 (StakeholderRequirement)
The Acquirer has selected the Rover 5 with encoders as its standard rover chassis.

##### 33 (StakeholderRequirement)
A unique feature of this chassis is the ability to adjust its height—and, therefore, the clearance under its body—by changing the angles at which the gearbox assemblies are mounted on the body. Interlocking teeth on the body and the gearboxes hold them in place and allow you to make adjustments in 5° increments by unscrewing a metal bracket inside the chassis, removing a gearbox, and reinserting it at a different angle. The elastic rubber tracks maintain sufficient tension with several different gearbox angles, allowing the chassis height to vary by nearly 1.5" (3.8 cm).

##### 35 (StakeholderRequirement)
The outer dimensions of the chassis are approximately 9.5" long, 9" wide, and 3" tall in its default, flattened configuration (with the front and rear gearboxes mounted at an angle of 180° to each other).

#### 36: Feature Summary (StakeholderRequirement)

##### 37 (StakeholderRequirement)
- durable plastic body
- 6-AA battery holder included
- two brushed DC motors with 210 mA free run and 2.4 A stall current at 7.2 V
- maximum speed of 10 in/s (25 cm/s) at 7.2 V
- ability to scale inclines limited only by friction
- height and clearance can be varied by adjusting gearbox angles
- version with encoders features two 333 CPR quadrature encoders (one for each track)
- dimensions: 9.5" × 9" × 3" (24.5 × 22.5 × 7.5 cm) in default configuration
- weight: 1.6 lb (0.72 kg)

#### 38: Expanding the Chassis (StakeholderRequirement)

##### 39 (StakeholderRequirement)
Thw Rover 3 chassis is compatible with the Dagu Electronics 1/8" acrylic RP5 expansion plates, which are available in narrow and wide versions and make it easy to add control electronics, sensors, wireless modules, servos, etc. The plates feature flexible mounting hole patterns and include four tapping screws to mount the plate to the chassis (although we have noticed a misalignment between the mounting holes on the expansion plates and the Rover 5, so you might only be able to secure two of the screws on opposing corners). The plates come in 8 colors:

#### 40: Using the Chassis (StakeholderRequirement)

##### 41 (StakeholderRequirement)
With only four motor leads and two battery leads, it is easy to interface the chassis with most dual motor controllers and robot controllers. Simply connect the battery holder leads to the controller’s power source and the motor leads to the controller’s motor driver outputs. Each set of motor leads is terminated with a female 3.96 mm pitch, 3-pin JST VH-style connector (the middle pin is not used), which our male premium jumper wires plug into nicely.

##### 42 (StakeholderRequirement)
The TReX Jr dual motor controller makes it easy to turn this chassis into a platform that can be controlled by RC signals or serial commands, or you can accomplish the same thing by pairing two of our newer Simple Motor Controllers. The Orangutan SV-328 or Baby Orangutan robot controllers work well with this chassis and make it easy to get an autonomous robot up and running (note: the stall current exceeds the ratings for these robot controllers, so make sure to avoid stalling the motors).

##### 43 (StakeholderRequirement)
The Rover 5 chassis with encoders has two additional bundles of wires, each containing the leads for the quadrature encoder’s 5 V power (red), ground (black), and signal (white and yellow) connections; the wires are individually terminated with female connectors that mate with 0.1" (2.54 mm) male headers. Our Pololu AVR Library provides wheel encoder functions that make it easy to use these encoders for position feedback on an Orangutan, and the Orangutan SVP (pictured above) has dedicated inputs for dual quadrature encoders and an auxiliary MCU preprogrammed to process encoder signals.

##### 44 (StakeholderRequirement)
The following shows a simple C program for the Orangutan robot controllers that gets the Rover 5 chassis moving:

###### 45 (StakeholderRequirement)
// Orangutan Rover 5 Demo Program
#include <avr/io.h> // provides ATmega-specific definitions/macros
#include <pololu/orangutan.h> // provides Pololu AVR library routines (LCD, motors, etc.)
int main()
{
clear(); // clear the LCD, set cursor to the start of the first LCD line
print("Tracked"); // print to the top line of the LCD
lcd_goto_xy(0, 1); // go to the start of the second LCD line
print("Chassis"); // print to the bottom line of the LCD
while (!button_is_pressed(ALL_BUTTONS)) {} // wait until a user button is pressed
delay_ms(500); // wait for 0.5 s
while (1) // loop forever
{
set_motors(255, 255);
delay_ms(5000);
set_motors(255, -255);
delay_ms(5000);
set_motors(-255, 255);
delay_ms(5000);
set_motors(-255, -255);
delay_ms(5000);
}
return 0;
}

## 25: Appendix (StakeholderRequirement)

### 26: Acronyms and abbreviations (StakeholderRequirement)
