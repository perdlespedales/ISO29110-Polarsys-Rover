# IBM Rational DOORS, 24 June 2015

# Specification: SyRS Template
- ReqIF.Description: Template for the System REquirements Specification
- ReqIF.Name: SyRS Template

## 1: Introduction (System Requirement)
- Type: Title

### 2: Purpose (System Requirement)
- Type: Title

### 3: Document conventions (System Requirement)
- Type: Title

### 4: Intended audience (System Requirement)
- Type: Title

### 5: Additional information (System Requirement)
- Type: Title

### 6: Contact information/SyRS team members (System Requirement)
- Type: Title

### 7: References (System Requirement)
- Type: Title

## 8: System overview (System Requirement)
- Type: Title

### 9: System context (System Requirement)
- Type: Title

### 10: System functions (System Requirement)
- Type: Title

### 11: User characteristics (System Requirement)
- Type: Title

## 12: Functional Requirements (System Requirement)
- Type: Title

### 35 (System Requirement)
Example System Functional Requirement 1
- Type: Requirement
- System Requirements Links -> 27

## 13: Usability Requirements (System Requirement)
- Type: Title

## 14: Performance Requirements (System Requirement)
- Type: Title

## 15: System Interfaces (System Requirement)
- Type: Title

## 16: System Operations (System Requirement)
- Type: Title

### 17: Human system integration requirements (System Requirement)
- Type: Title

### 18: Maintainability (System Requirement)
- Type: Title

### 19: Reliability (System Requirement)
- Type: Title

## 20: System modes and states (System Requirement)
- Type: Title

## 21: Physical characteristics (System Requirement)
- Type: Title

### 22: Physical requirements (System Requirement)
- Type: Title

### 23: Adaptability requirements (System Requirement)
- Type: Title

## 24: Environmental conditions (System Requirement)
- Type: Title

## 25: System security (System Requirement)
- Type: Title

## 26: Information management (System Requirement)
- Type: Title

## 27: Policies and regulations (System Requirement)
- Type: Title

## 28: System life cycle sustainment (System Requirement)
- Type: Title

## 29: Packaging, handling, shipping and transportation (System Requirement)
- Type: Title

## 30: Verification (System Requirement)
- Type: Title

## 31: Assumptions and dependencies (System Requirement)
- Type: Title

## 32: Other Requirements (System Requirement)
- Type: Title

## 33: Appendix A: Terminology/Glossary/Definitions list (System Requirement)
- Type: Title

## 34: Appendix B: Requirements Traceability Matrix (System Requirement)
- Type: Title

# Specification: StRS Template
- ReqIF.Description: System RE DP Stakeholder Requirements Specification Template
- ReqIF.Name: StRS Template

## 1: Introduction (Stakeholder Requirement)

### 2: Business purpose (Stakeholder Requirement)

### 3: Business scope (Stakeholder Requirement)

### 4: Business overview (Stakeholder Requirement)

### 5: Definitions (Stakeholder Requirement)

### 6: Stakeholders (Stakeholder Requirement)

## 7: References (Stakeholder Requirement)

## 8: Business management requirements (Stakeholder Requirement)

### 9: Business environment (Stakeholder Requirement)

### 10: Goal and objective (Stakeholder Requirement)

### 11: Business model (Stakeholder Requirement)

### 12: Information environment (Stakeholder Requirement)

## 13: Business operational requirements (Stakeholder Requirement)

### 14: Business processes (Stakeholder Requirement)

### 15: Business operational policies and rules (Stakeholder Requirement)

### 16: Business operational constraints (Stakeholder Requirement)

### 17: Business operational modes (Stakeholder Requirement)

### 18: Business operational quality (Stakeholder Requirement)

### 19: Business structure (Stakeholder Requirement)

## 20: User requirements (Stakeholder Requirement)

### 27 (Stakeholder Requirement)
Example Stakeholder Requirement 1

## 21: Concept of proposed system (Stakeholder Requirement)

### 22: Operational concept (Stakeholder Requirement)

### 23: Operational scenario (Stakeholder Requirement)

## 24: Project Constraints (Stakeholder Requirement)

## 25: Appendix (Stakeholder Requirement)

### 26: Acronyms and abbreviations (Stakeholder Requirement)
